module nrcelldu-prach-extensions {
    yang-version 1.1;
    namespace "urn:srsran-nrcelldu-prach-extension:1.0";
    prefix "srsran-nrcelldu-prach";
    
    organization "Software Radio Systems Ltd";
    description "The module defines YANG extensions needed for srsRAN
                 Copyright (c) 2024-2025 Software Radio Systems. All rights reserved.";
    revision 2025-01-08 { description "Initial version"; }

    grouping prach_extensions_subtree {
        description "srsRAN Extension of 3gpp PRACH config";

        container srs_nrcelldu_prach_extensions {
            leaf prach_root_sequence_index {
                description "PRACH root sequence index, see TS 38.211, clause 6.3.3.1.";
                type prach_root_seq_index_value;
                default "1";
            }
        }        
    }

    typedef prach_root_seq_index_value {
        type int32 { range 1..839; }
    }
}
